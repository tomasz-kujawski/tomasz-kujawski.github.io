FME workspace vind_hele_norge.fmw

Parameters:
- SourceDataset_GEODATABASE_FILE = C:\Users\tok\Documents\GIS vind\Vinddata_tomasz.gdb\Vinddata_tomasz.gdb   # File Geodatabase
- SourceDataset_SHAPEFILE_5 = C:\Users\tok\Documents\GIS vind\Boliger 250m 2025\Boliger 250m 2025.shp   # Source Esri Shapefile(s)
- SourceDataset_SHAPEFILE_7 = C:\Users\tok\Documents\GIS vind\Bygningsmassen 250m 2025\Bygningsmassen 250m 2025.shp   # Source Esri Shapefile(s)
- SourceDataset_SHAPEFILE_6 = C:\Users\tok\Documents\GIS vind\Tettbygde fritidsbyggområder 2025\Tettbygde fritidsbyggområder 2025.shp   # Source Esri Shapefile(s)
- SourceDataset_SHAPEFILE = C:\Users\tok\Documents\GIS vind\Bedrifter 250m 2026\Bedrifter 250m 2026.shp   # Source Esri Shapefile(s)
- SourceDataset_GEODATABASE_FILE_3 = C:\Users\tok\Documents\GIS vind\Energi_0000_Norge_25833_Nettanlegg_FGDB\Energi_0000_Norge_25833_Nettanlegg_FGDB.gdb   # File Geodatabase
- SourceDataset_COG_3 = C:\Users\tok\Documents\hele norge vind\NVE_47551B14_1779872810726_2800\NVEKartdata\NVEData\Vindressurs\Vindressurs_Gjennomsnittsvind_120m.tif   # Source GeoTIFF File(s) or URL(s)
- DestDataset_GEOTIFF = C:\Users\tok\Documents\hele norge vind FME   # Destination GeoTIFF Folder

Readers:
- GEODATABASE_FILE_1: GEODATABASE_FILE from $(SourceDataset_GEODATABASE_FILE)
- SHAPEFILE_1: SHAPEFILE from $(SourceDataset_SHAPEFILE)
- SHAPEFILE_2: SHAPEFILE from $(SourceDataset_SHAPEFILE_5)
- SHAPEFILE_3: SHAPEFILE from $(SourceDataset_SHAPEFILE_7)
- SHAPEFILE_4: SHAPEFILE from $(SourceDataset_SHAPEFILE_6)
- GEODATABASE_FILE_2: GEODATABASE_FILE from $(SourceDataset_GEODATABASE_FILE_3)
- COG_2: COG from $(SourceDataset_COG_3)

Writers:
- GEOTIFF_1: GEOTIFF to $(DestDataset_GEOTIFF)

Reprojector_3
    DEST = EUREF89.NTM-10
    INTERPOLATION_TYPE = NearestNeighbor
    RASTER_CELL_SIZE = PreserveCells
    RASTER_TOLERANCE = 0.0
    REPROJECTED -> Bufferer
3DForcer
    KEEPZVAL = No
    ZVALATTR = 1
    -> NumericRasterizer
NumericRasterizer
    ANTI_ALIASING = No
    BACKGROUND_VALUE = 0
    COLUMNS = 1763
    FILL_WITH_NODATA = Yes
    INTERPRETATION_TYPE_LOOKUP = REAL64
    ROWCOL_OR_CELLSIZE = RowsColumns
    ROWS = 2322
    SPECIFY_GROUND_EXTENTS = Use input data ground extents
    TOLERANCE = 0.5
    INTERPRETATION_TYPE = Real64
    RASTER -> RasterToPolygonCoercer
RasterToPolygonCoercer
    EXTRACT_NODATA = No
    LABEL_ATTRIBUTE = _label
    PRESERVE_ATTRIBUTES_LOOKUP = YES
    EXTRACT_NODATA_LOOKUP = No
    PRESERVE_ATTRIBUTES = Yes
    POLYGONS -> AreaOnAreaOverlayer [AREA]
Reprojector_4
    DEST = EUREF89.NTM-10
    INTERPOLATION_TYPE = NearestNeighbor
    RASTER_CELL_SIZE = PreserveCells
    RASTER_TOLERANCE = 0.0
    REPROJECTED -> Bufferer_2
Note: avstand 800m fra bygg
Bufferer_2
    ANGLE = 22.5
    CAP_STYLE_LOOKUP = CAP_ARC
    CORNER_STYLE_LOOKUP = JOIN_ARC
    MODE = AREA
    OFFSET = 800
    OFFSET_UNITS = METERS
    PRECISION = APPROX
    CAP_STYLE = Arc
    CORNER_STYLE = Arc
    BUFFERED -> Dissolver_2
Dissolver_2
    ACCUM_INPUT_ATTRS_LOOKUP = One
    CLEANING_TOLERANCE_LOOKUP = AUTO
    CONNECT_Z_MODE_LOOKUP = FIRST_WINS
    DEAGGREGATE_INPUT = Yes
    AREA -> Clipper_5 [CLIPPER]
Reprojector_5
    DEST = EUREF89.NTM-10
    INTERPOLATION_TYPE = NearestNeighbor
    RASTER_CELL_SIZE = PreserveCells
    RASTER_TOLERANCE = 0.0
    REPROJECTED -> Clipper [CLIPPER]
Reprojector_2
    DEST = EUREF89.NTM-10
    INTERPOLATION_TYPE = NearestNeighbor
    RASTER_CELL_SIZE = PreserveCells
    RASTER_TOLERANCE = 0.0
    REPROJECTED -> RasterPropertyExtractor
RasterPropertyExtractor
    -> RasterExpressionEvaluator [A]
Note: vind sterkere enn 6.5 m/s
RasterExpressionEvaluator
    EXPRESSION_LIST = AUTO if(A[0]>6.5, 1, 0)
    MODE = One Raster
    RESULT -> Clipper [CANDIDATE]
Note: Klipp av hav
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Clipper_2 [CANDIDATE]
Reprojector_6
    DEST = EUREF89.NTM-10
    INTERPOLATION_TYPE = NearestNeighbor
    RASTER_CELL_SIZE = PreserveCells
    RASTER_TOLERANCE = 0.0
    REPROJECTED -> Clipper_2 [CLIPPER]
Note: Klipp av untakk vern
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> Clipper_5 [CANDIDATE]
Note: Klipp av alle bygg
Clipper_5
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> RasterToPolygonCoercer_2
RasterToPolygonCoercer_2
    EXTRACT_NODATA = No
    LABEL_ATTRIBUTE = _label
    PRESERVE_ATTRIBUTES_LOOKUP = YES
    EXTRACT_NODATA_LOOKUP = No
    PRESERVE_ATTRIBUTES = Yes
    POLYGONS -> AreaOnAreaOverlayer [AREA]
AreaOnAreaOverlayer
    ACCUM_ATTRS = ONE
    CLEANING_TOLERANCE_LOOKUP = AUTO
    CONNECT_Z_MODE_LOOKUP = FIRST_WINS
    DEAGGREGATE_INPUT = Yes
    OVC_ATTR = _overlaps
    ACCUM_ATTRS_NAME = Use Attributes From One Feature
    CLEANING_TOLERANCE = Automatic
    CONNECT_Z_MODE = First Wins
    AREA -> Tester_2
Tester_2
    BOOL_OP = OR
    TEST_CLAUSE = TEST @Value(_overlaps) > 1
    TEST_MODE = TEST
    PASSED -> 3DForcer_2
3DForcer_2
    KEEPZVAL = No
    ZVALATTR = 1
    -> NumericRasterizer_2
NumericRasterizer_2
    ANTI_ALIASING = No
    BACKGROUND_VALUE = 0
    COLUMNS = 1763
    FILL_WITH_NODATA = Yes
    INTERPRETATION_TYPE_LOOKUP = REAL64
    ROWCOL_OR_CELLSIZE = RowsColumns
    ROWS = 2322
    SPECIFY_GROUND_EXTENTS = Use input data ground extents
    TOLERANCE = 0.5
    INTERPRETATION_TYPE = Real64
    RASTER -> Raster1 (writer GEOTIFF_1)
Raster1 (writer GEOTIFF_1)

Bookmark: bygninger
Tettbygde fritidsbyggområder 2025 (reader SHAPEFILE_4)
    attributes: KOMMUNENR varchar(80), Omraade_ID varchar(80), Omraadestr varchar(80), TotArea_m2 double, Area_m2_iK double, Shape_Leng double, Shape_Area double
    -> Reprojector_4
Bygningsmassen 250m 2025 (reader SHAPEFILE_3)
    attributes: ssbid0250m varchar(80), ssbid0100m number(18,0), Bygninger_ double, Uoppgitt double, N1_1_Bolig double, N1_2_Indus double, N1_3_Konto double, N1_4_Samfe double, N1_5_Hotel double, N1_6_Kultu double, N1_7_Helse double, N1_8_Fengs double, N2_11_Eneb double, N2_12_Toma double, N2_13_Rekk double, N2_14_Boli double, N2_15_Bygn double, N2_16_Frit double, N2_17_Koie double, N2_18_Gara double, N2_19_Anne double, N2_21_Indu double, N2_22_Ener double, N2_23_Lage double, N2_24_Fisk double, N2_31_Kont double, N2_32_Forr double, N2_33_Mess double, N2_41_Eksp double, N2_42_Tele double,
      N2_43_Gara double, N2_44_Vegt double, N2_51_Hote double, N2_52_Over double, N2_53_Rest double, N2_61_Skol double, N2_62_Univ double, N2_64_Muse double, N2_65_Idre double, N2_66_Kult double, N2_67_Reli double, N2_71_Syke double, N2_72_Syke double, N2_73_Prim double, N2_81_Feng double, N2_82_Bere double, N2_83_Monu double, N2_84_Offe double
    -> Reprojector_4
Bedrifter 250m 2026 (reader SHAPEFILE_1)
    attributes: SSBID250M number(18,0), est_tot long, emp_tot long
    -> Reprojector_4
Boliger 250m 2025 (reader SHAPEFILE_2)
    attributes: SSBID0250M number(18,0), dwe_todw long, dwe_det long, dwe_2dw long, dwe_row long, dwe_mult long, dwe_com long, dwe_oth long, dwe_area long
    -> Reprojector_4

Bookmark: El
el_transformatorstasjon (reader GEODATABASE_FILE_2)
    attributes: OBJECTID integer, objtype char(32), drifter char(100), kildelokalid char(25), drifterorgnr integer, driftsattar integer, driftsmerking char(100), eier char(100), eierorgnr integer, lokalid char(100), navnerom char(100), versjonid char(100), kilde char(100), kildedato date, kildeendretdato date, kildeorgnr integer, navn char(100), nettniva char(30), nveopprettetdato date, spenning double, komponentkodeverdi integer, komponentkodesystem char(15), malemetode integer, noyaktighet integer, status char(50), antallbrytere integer, medium char(1), sysbasid integer, antallgeneratorer integer, antalltrafoer integer,
      totalytelsegeneratorer double, totalytelsetrafoer double, type char(30)
    -> Reprojector_3
el_luftlinje (reader GEODATABASE_FILE_2)
    attributes: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
el_mast (reader GEODATABASE_FILE_2)
    attributes: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
el_sjokabel (reader GEODATABASE_FILE_2)
    attributes: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

Bookmark: el
Bufferer
    ANGLE = 22.5
    CAP_STYLE_LOOKUP = CAP_ARC
    CORNER_STYLE_LOOKUP = JOIN_ARC
    MODE = AREA
    OFFSET = 2000
    OFFSET_UNITS = METERS
    PRECISION = APPROX
    CAP_STYLE = Arc
    CORNER_STYLE = Arc
    BUFFERED -> Dissolver
Note: transformator < 2km
Dissolver
    ACCUM_INPUT_ATTRS_LOOKUP = One
    CLEANING_TOLERANCE_LOOKUP = AUTO
    CONNECT_Z_MODE_LOOKUP = FIRST_WINS
    DEAGGREGATE_INPUT = Yes
    AREA -> 3DForcer

Bookmark: untakk
Harde_innflyvningssoner (reader GEODATABASE_FILE_1)
    attributes: OBJECTID integer, Id integer, gridcode integer, Shape_Length double, Shape_Area double
    -> Reprojector_6
Harde_verdensarvUNESCO (reader GEODATABASE_FILE_1)
    attributes: OBJECTID integer, Id integer, gridcode integer, Shape_Length double, Shape_Area double
    -> Reprojector_6
Harde_Innsjoer (reader GEODATABASE_FILE_1)
    attributes: OBJECTID integer, Id integer, gridcode integer, Shape_Length double, Shape_Area double
    -> Reprojector_6
Harde_isbreer (reader GEODATABASE_FILE_1)
    attributes: OBJECTID integer, Id integer, gridcode integer, Shape_Length double, Shape_Area double
    -> Reprojector_6
Harde_tettsteder (reader GEODATABASE_FILE_1)
    attributes: OBJECTID integer, Id integer, gridcode integer, Shape_Length double, Shape_Area double
    -> Reprojector_6
Harde_vern (reader GEODATABASE_FILE_1)
    attributes: OBJECTID integer, Id integer, gridcode integer, Shape_Length double, Shape_Area double
    -> Reprojector_6

Bookmark: fylker
Fylker (reader GEODATABASE_FILE_1)
    attributes: OBJECTID integer, objtype char(32), fylke smallint, fylke_id char(2), fylkesnavn char(50), fylkesnr smallint, navn char(60), maxsimptol double, minsimptol double, shape_Length double, shape_Area double
    -> Reprojector_5

Bookmark: vind
COG (reader COG_2)
    -> Reprojector_2
